module distributednat {
    yang-version 1;
    namespace "urn:opendaylight:params:xml:ns:yang:distributednat";
    prefix "distributednat";

    revision "2015-01-05" {
        description "Initial revision of distributednat model";
    }
}
