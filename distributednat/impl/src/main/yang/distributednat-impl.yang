module distributednat-impl {
    yang-version 1;
    namespace "urn:opendaylight:params:xml:ns:yang:distributednat:impl";
    prefix "distributednat-impl";

    import config { prefix config; revision-date 2013-04-05; }
    import opendaylight-md-sal-binding { prefix md-sal-binding; revision-date 2013-10-28;}

    description
        "Service definition for distributednat project";

    revision "2014-12-10" {
        description
            "Initial revision";
    }

    identity distributednat {
        base config:module-type;
        config:java-name-prefix Distributednat;
    }

    augment "/config:modules/config:module/config:configuration" {
        case distributednat {
            when "/config:modules/config:module/config:type = 'distributednat'";
            container broker {
                uses config:service-ref {
                    refine type {
                        mandatory true;
                        config:required-identity md-sal-binding:binding-broker-osgi-registry;
                    }
                }
            }

            container notification-service {
                uses config:service-ref {
                    refine type {
                        mandatory true;
                        config:required-identity md-sal-binding:binding-notification-service;
                    }
                }
            }
        }
    }
}
